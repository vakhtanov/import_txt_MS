Attribute VB_Name = "Place_line_by_xyz_file"
Sub ReadFile_placePoint()
'THIS IS REALY WORK
Dim iFile As Integer
Dim sLine As String
Dim ar() As String

Dim m_atPoints(0 To 1) As Point3d
Dim CuLine As LineElement

Dim x As Double
Dim y As Double
Dim z As Double


iFile = FreeFile

Open "d:\LEP201711_ira\0Scripts_VBA_for_MS\lep_test.txt" For Input As iFile
' Доработки: Читать координаты с выделенного объекта и в узлах рисовать палки
' А еще просить выделить 1й элемент, потом второй и рисовать палки!
Do
    Line Input #iFile, sLine
    ar = Split(sLine, ",")
    If UBound(ar) = 2 Then
        x = Val(ar(0))
        y = Val(ar(1))
        z = Val(ar(2))
        m_atPoints(0).x = x
        m_atPoints(0).y = y
        m_atPoints(0).z = z
'Здесь уже можно реализовать задумку, только в файл добавить еще координат
'Проблема - в новом МС нет функции экспорта координат!.
        m_atPoints(1).x = x
        m_atPoints(1).y = y + 10
        m_atPoints(1).z = z
        
        'draws the line segment
        Set CuLine = CreateLineElement1(Nothing, m_atPoints)
        ActiveModelReference.AddElement CuLine
        CuLine.Redraw
        '____________________
        
        ' process point...
        'Debug.Print x, y, z, s
    End If

Loop Until EOF(iFile)

Close iFile
End Sub

Sub ReadFile_DIALOG_placePoint()
    Dim fd As OpenFileDialog
    'Declare a variable for the directory path.
    Dim directory As String
    'Set the directory path
    directory = "C:\"
    'Create a FileDialog object as a File Picker dialog box.
    Set fd = Application.FileDialog(msoFileDialogFilePicker)
    'Declare a variable to contain the path
    'of each selected item. Even though the path is aString,
    'the variable must be a Variant because For Each...Next
    'routines only work with Variants and Objects.
    Dim vrtSelectedItem As Variant

    'Use a With...End With block to reference the FileDialog object.
    With fd
        'Change the initial directory\filename
        .InitialFileName = directory
        'Use the Show method to display the File Picker dialog box and return the user's action.
        'The user pressed the button.
        If .Show = -1 Then

            'Step through each string in the FileDialogSelectedItems collection.
            For Each vrtSelectedItem In .SelectedItems

                'vrtSelectedItem is aString that contains the path of each selected item.
                'You can use any file I/O functions that you want to work with this path.
                'This example displays the path in a message box.
                MsgBox "The path is: " & vrtSelectedItem

            Next vrtSelectedItem
        'The user pressed Cancel.
        Else
        End If
    End With

    'THIS IS REALY WORK
    Dim iFile As Integer
    Dim sLine As String
    Dim ar() As String

    Dim m_atPoints(0 To 1) As Point3d
    Dim CuLine As LineElement

    Dim x As Double
    Dim y As Double
    Dim z As Double


iFile = FreeFile

Open "d:\LEP201711_ira\0Scripts_VBA_for_MS\lep_test.txt" For Input As iFile
' Доработки: Читать координаты с выделенного объекта и в узлах рисовать палки
' А еще просить выделить 1й элемент, потом второй и рисовать палки!
Do
    Line Input #iFile, sLine
    ar = Split(sLine, ",")
    If UBound(ar) = 2 Then
        x = Val(ar(0))
        y = Val(ar(1))
        z = Val(ar(2))
        m_atPoints(0).x = x
        m_atPoints(0).y = y
        m_atPoints(0).z = z
'Здесь уже можно реализовать задумку, только в файл добавить еще координат
'Проблема - в новом МС нет функции экспорта координат!.
        m_atPoints(1).x = x
        m_atPoints(1).y = y + 10
        m_atPoints(1).z = z
        
        'draws the line segment
        Set CuLine = CreateLineElement1(Nothing, m_atPoints)
        ActiveModelReference.AddElement CuLine
        CuLine.Redraw
        '____________________
        
        ' process point...
        'Debug.Print x, y, z, s
    End If

Loop Until EOF(iFile)

Close iFile
End Sub

Attribute VB_Name = "clsPlaceLineCommand"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'
'  Copyright: (c) 2004 Bentley Systems, Incorporated. All rights reserved.
'
'---------------------------------------------------------------------
'Class Implementation for PLACELINE Example
'Description: This command draws simple line segments by connecting the
'             data points provided by the user.
'---------------------------------------------------------------------
Option Explicit

Implements IPrimitiveCommandEvents

'----------------------------------------------------------------------
'
'           Private Data Members
'
'----------------------------------------------------------------------
Private m_atPoints(0 To 1) As Point3d
Private m_nPoints As Integer

Private Sub IPrimitiveCommandEvents_Cleanup()

End Sub

Private Sub IPrimitiveCommandEvents_DataPoint(Point As Point3d, ByVal View As View)
If m_nPoints = 0 Then 'user has entered Startpoint of the line segment
    CommandState.StartDynamics
    m_atPoints(0) = Point
    m_nPoints = 1
    ShowPrompt "Place end point"
ElseIf m_nPoints = 1 Then 'user has entered Endpoint of the line segment
    m_atPoints(1) = Point
    
    'draws the line segment
    Dim oLineEl As LineElement
    Set oLineEl = CreateLineElement1(Nothing, m_atPoints)
    ActiveModelReference.AddElement oLineEl
    oLineEl.Redraw
    
    'set Startpoint for next line segment to the Endpoint of the previous one
    m_atPoints(0) = m_atPoints(1)
End If
End Sub


Private Sub IPrimitiveCommandEvents_Dynamics(Point As Point3d, ByVal View As View, ByVal DrawMode As MsdDrawingMode)
'method called to show dynamics

If m_nPoints = 1 Then
    m_atPoints(1) = Point
    
    'display the temporary line element
    Dim oLineEl As LineElement
    Set oLineEl = CreateLineElement1(Nothing, m_atPoints)
    oLineEl.Color = 5 ' color to indicate its a temporary display
    oLineEl.Redraw DrawMode
End If
End Sub

Private Sub IPrimitiveCommandEvents_Keyin(ByVal KeyIn As String)

End Sub

Private Sub IPrimitiveCommandEvents_Reset()
' method called when the reset event occurs

' On reset, start the command again.
CommandState.StartPrimitive Me
m_nPoints = 0
End Sub

Private Sub IPrimitiveCommandEvents_Start()
'method called at the start of the command

ShowCommand "VBA PlaceLine Example"
ShowPrompt "Select start of line"
End Sub

Attribute VB_Name = "modPlaceShapeCommands"
Option Explicit
Sub myStartUpCommand()

Dim m_atPoints(0 To 1) As Point3d
Dim CuLine As LineElement
'Dim x As Double
'Dim y As Double
'Dim z As Double

m_atPoints(0).x = 10#
m_atPoints(0).y = 11#
m_atPoints(0).z = 12#

m_atPoints(1).x = 15#
m_atPoints(1).y = 16#
m_atPoints(1).z = 17#

'draws the line segment
Set CuLine = CreateLineElement1(Nothing, m_atPoints)
ActiveModelReference.AddElement CuLine
CuLine.Redraw
'____________________

ShowCommand "myKeyinMacro"
ShowPrompt "Running custom setup macro"

With CadInputQueue
   .SendKeyin "active color green"
   .SendKeyin "active level 10"
   .SendKeyin "history initialize"
   .SendKeyin "popset on"
   .SendKeyin "accudraw shortcuts default"
End With
 

ShowPrompt "Setup complete. Ready for user input."

End Sub




Sub ReadFile()
   Dim iFile As Integer
Dim sLine As String
Dim ar() As String

Dim x As Double
Dim y As Double
Dim z As Double
Dim s As String

iFile = FreeFile

Open "d:\LEP201711_ira\lep_test.txt" For Input As iFile

Do

    Line Input #iFile, sLine
   
    ar = Split(sLine, ",")
   
    If UBound(ar) = 3 Then
        x = Val(ar(0))
        y = Val(ar(1))
        z = Val(ar(2))
        s = ar(3)
        ' process point...
        Debug.Print x, y, z, s
    End If

Loop Until EOF(iFile)

Close iFile
End Sub
Sub PlaceLine()
    CommandState.StartPrimitive New clsPlaceLineCommand
End Sub
